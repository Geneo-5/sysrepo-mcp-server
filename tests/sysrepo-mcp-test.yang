/// SPDX-License-Identifier: BSD-3-Clause
///
/// This file is part of sysrepo-mcp.
/// Copyright (C) 2026 Loic JOURDHEUIL SELLIN <46419549+Geneo-5@users.noreply.github.com>

/// Test module that exercises every type covered by get_schema:
/// uint8/16/32/64, int8/16/32/64, string (with range, length, patterns
/// with length + pattern), binary, boolean, enumeration, bits,
/// empty, decimal64, identityref, leafref, union, and containers/lists.

module sysrepo-mcp-test {
    yang-version 1.1;

    namespace "urn:sysrepo-mcp:test";
    prefix "sr-mcp-test";

    import ietf-netconf-acm {
        prefix "nacm";
        reference
            "RFC 8341: Network Configuration Access Control Model";
    }

    revision "2026-09-25" {
        description
            "Test module covering all get_schema type cases.";
    }

    /* --- types exercised by get_schema --- */

    typedef mac-address {
        type string {
            length "12..17";
            pattern "([0-9a-f]{2}:){5}[0-9a-f]{2}";
        }
        description "MAC address as a string with length + pattern.";
    }

    typedef my-binary {
        type binary;
        description "Plain binary type.";
    }

    identity my-identity {
        description "Test identity.";
    }

    identity my-derived {
        base my-identity;
        description "Identity derived from my-identity.";
    }

    typedef my-identityref {
        type identityref {
            base my-identity;
        }
        description "Identityref with explicit base.";
    }

    /* --- data nodes --- */

    list api-key {
        when "true()";
        must "string-length(key) > 0";
        key "key";

        nacm:default-deny-all;

        description
            "API keys accepted by the server, each bound to a NACM user.

             This is a test mirror of the production module; the keys
             listed here are never used for authentication (the test
             fixture docker/sysrepo-mcp.conf holds the real keys).";

        leaf key {
            type string {
                length "16..256";
            }
            description
                "The API key.";
        }

        leaf user {
            type nacm:user-name-type;
            mandatory true;
            description
                "NACM user name this key maps to.";
        }

        leaf description {
            type string;
            description
                "Free-form note identifying the agent this key was issued
                 to.";
        }
    }

    container server-state {
        config false;

        description
            "Operational state of the server (test mirror).";

        leaf version {
            type string;
            description
                "Version of the running server.";
        }

        leaf uptime-seconds {
            type uint64;
            units "seconds";
            description
                "Time elapsed since the server started.";
        }

        leaf active-sessions {
            type uint32;
            description
                "Number of MCP sessions currently alive.";
        }

        leaf max-sessions {
            type uint32;
            description
                "Maximum number of concurrent MCP sessions.";
        }

        leaf mac {
            type mac-address;
            description
                "String with length constraint and pattern.";
        }

        leaf binary-data {
            type my-binary;
            description
                "Binary type.";
        }

        leaf identity-ref-val {
            type my-identityref;
            description
                "Identityref with explicit base.";
        }

        leaf union-val {
            type union {
                type string;
                type uint8;
            }
            description
                "Union type: string or uint8.";
        }

        leaf nested-union-val {
            type union {
                type union {
                    type string;
                    type uint16;
                }
                type int32;
            }
            description
                "Nested union: (string | uint16) | int32.";
        }

        leaf bits-val {
            type bits {
                bit flag-1 {
                    position 0;
                    description "First flag.";
                }
                bit flag-2 {
                    position 1;
                    description "Second flag.";
                }
            }
            description
                "Bits type.";
        }

        leaf empty-val {
            type empty;
            description
                "Empty type.";
        }

        list session {
            key "session-id";

            description
                "Live MCP sessions (test mirror).";

            leaf session-id {
                type string;
                description
                    "Session identifier.";
            }

            leaf created {
                type uint64;
                units "seconds";
                description
                    "Creation time, as a Unix timestamp.";
            }

            leaf last-activity {
                type uint64;
                units "seconds";
                description
                    "Time of the last request on this session.";
            }

            leaf user {
                type nacm:user-name-type;
                description
                    "NACM user the session is authenticated as.";
            }

            leaf subscriptions {
                type uint32;
                description
                    "Notification subscriptions open on this session.";
            }

            leaf pending-notifications {
                type uint32;
                description
                    "Notifications queued and not yet collected by a poll.";
            }

            leaf dropped-notifications {
                type uint64;
                description
                    "Notifications lost to queue overflow since the session
                     was created.";
            }
        }
    }
}
