module sysrepo-mcp {
    yang-version 1.1;

    namespace "urn:sysrepo-mcp:server";
    prefix sr-mcp;

    import ietf-netconf-acm {
        prefix nacm;
        reference
            "RFC 8341: Network Configuration Access Control Model";
    }

    organization
        "sysrepo-mcp project";

    contact
        "Loic JOURDHEUIL SELLIN
         <46419549+Geneo-5@users.noreply.github.com>";

    description
        "Runtime configuration and operational state of the sysrepo-mcp
         server.

         Anything an operator must be able to change without recompiling
         belongs here; everything fixed at build time is in config.in.

         Copyright (C) 2026 Loic JOURDHEUIL SELLIN.
         SPDX-License-Identifier: LGPL-3.0-only";

    revision 2026-09-19 {
        description
            "Add the subscription and notification counters of a session, so
             the operational view matches what the get_status tool reports.";
    }

    revision 2026-09-18 {
        description
            "Set yang-version 1.1, type the NACM user name with
             nacm:user-name-type, and deny the API key list by default.";
    }

    revision 2026-09-14 {
        description
            "Initial revision.";
    }

    list api-key {
        key "key";

        nacm:default-deny-all;

        description
            "API keys accepted by the server, each bound to a NACM user.

             A request presenting one of these keys is processed with the
             access rights of the associated NACM user.

             This list is denied to everybody by default: a principal able to
             read it can impersonate every agent, and a principal able to
             write it can grant itself any NACM identity. Grant access to it
             deliberately, and to as few users as possible.";

        leaf key {
            type string {
                length "16..256";
            }
            description
                "The API key.

                 Stored as presented today, which means in the clear. It
                 should hold a hash instead; see the roadmap. Until then,
                 treat the datastore as holding a credential.";
        }

        leaf user {
            type nacm:user-name-type;
            mandatory true;
            description
                "NACM user name this key maps to.

                 It must match a user named in the groups of
                 ietf-netconf-acm; sysrepo evaluates its rules against this
                 name. An unknown name is not an error here, but it leaves
                 the key with only the rights of the default NACM policy.";
        }

        leaf description {
            type string;
            description
                "Free-form note identifying the agent this key was issued
                 to, so a key can be revoked without guessing who uses it.";
        }
    }

    container server-state {
        config false;

        description
            "Operational state of the server.

             The same information is available through the get_status MCP
             tool, which exists so that a liveness probe does not need read
             access to the datastore.";

        leaf version {
            type string;
            description
                "Version of the running server.";
        }

        leaf uptime-seconds {
            type uint64;
            units "seconds";
            description
                "Time elapsed since the server started.";
        }

        leaf active-sessions {
            type uint32;
            description
                "Number of MCP sessions currently alive.";
        }

        leaf max-sessions {
            type uint32;
            description
                "Maximum number of concurrent MCP sessions.";
        }

        list session {
            key "session-id";

            description
                "Live MCP sessions.

                 This list is the shared session store: with a FastCGI
                 max-procs above 1, consecutive requests from one agent land
                 in different processes, so process-local state cannot work.";

            leaf session-id {
                type string;
                description
                    "Session identifier, as carried by the Mcp-Session-Id
                     HTTP header.";
            }

            leaf created {
                type uint64;
                units "seconds";
                description
                    "Creation time, as a Unix timestamp.";
            }

            leaf last-activity {
                type uint64;
                units "seconds";
                description
                    "Time of the last request on this session, as a Unix
                     timestamp. Idle expiry is measured from here.";
            }

            leaf user {
                type nacm:user-name-type;
                description
                    "NACM user the session is authenticated as.";
            }

            leaf subscriptions {
                type uint32;
                description
                    "Notification subscriptions open on this session.";
            }

            leaf pending-notifications {
                type uint32;
                description
                    "Notifications queued and not yet collected by a poll.";
            }

            leaf dropped-notifications {
                type uint64;
                description
                    "Notifications lost to queue overflow since the session
                     was created.

                     A non-zero value means the agent polls too slowly, or
                     watches more than it needs to.";
            }
        }
    }
}
